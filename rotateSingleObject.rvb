Option Explicit
'Script written by Houtan Bastani
'Script copyrighted by Houtan Bastani

'This function rotates a shape specified by the user about
'a point specified by the user. Rotation is done in all
'three directions.

Call Main()
Sub Main()
	Dim obj, box, center, xyp
	obj = Rhino.GetObject("Which object should we rotate?", 0, True)
	If Not IsNull(obj) Then
		box = Rhino.BoundingBox(obj)
		If IsArray(box) Then
			Randomize
			center = Rhino.GetPoint("About which point?")
			xyp = Rhino.WorldXYPlane()
			Rhino.RotateObject obj, center, Rnd * 360, xyp(1)
			Rhino.RotateObject obj, center, Rnd * 360, xyp(2)
			Rhino.RotateObject obj, center, Rnd * 360, xyp(3)
		End If
	End If
End Sub
